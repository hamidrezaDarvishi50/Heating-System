# req

## #1: Doer (Container)

### #14: کنترل دما (Functional)
دمای هر اتاق باید به طور پیوسته بر اساس معادله دیفرانسیل داده شده محاسبه شود (شامل تاثیر همسایه‌ها، دمای بیرون و وضعیت بخاری).

### #15: منطق روشن/خاموش (Functional)

#### #16: ترموستات روشن (Functional)
اگر بخاری در اتاق i موجود باشد و دما کمتر یا مساوی حد پایین باشد، بخاری باید روشن شود

#### #17: ترموستات خاموش (Functional)
اگر بخاری در اتاق i موجود باشد و دما بیشتر یا مساوی حد بالا باشد، بخاری باید خاموش شود

### #18: شرایط انتقال (Container)

#### #19: شرط وجود (Functional)
بخاری تنها می‌تواند از اتاق j به i منتقل شود که اتاق i بخاری نداشته باشد و اتاق j بخاری داشته باشد.

#### #20: شرط دما (Functional)
انتقال بخاری به اتاق i تنها زمانی مجاز است که دمای فعلی اتاق i کمتر از آستانه دریافت (geti​) باشد.

#### #21: شرط اختلاف (Functional)
انتقال بخاری از j به i تنها زمانی مجاز است که اختلاف دما (xi​−xj​) کمتر از آستانه اختلاف (difi​) باشد

## #7: Checker (Container)
در هر لحظه از زمان، مجموع تعداد بخاری‌های فعال در کل خانه نباید بیشتر از ۲ عدد باشد
- Keywords: safety

### #22: محدودیت تعداد بخاری (Functional)
انتقال بخاری از j به i تنها زمانی مجاز است که اختلاف دما (xi​−xj​) کمتر از آستانه اختلاف (difi​) باشد

### #23: تأیید جابجایی (Functional)
واحد ایمنی باید بررسی کند که جابجایی بخاری‌ها قوانین منطقی (مثل عدم وجود دو بخاری در یک اتاق) را نقض نکند.

## #8: بازه دمایی مطلوب (Functional)
سیستم باید بتواند دمای تمام اتاق‌ها را در بازه ۱۵ تا ۲۰ درجه سانتی‌گراد نگه دارد.
- Keywords: safety

## #24: Gateway Logic (Functional)
فرمان نهایی بخاری (ActuatorActuatorActuator) باید برابر با فرمان واحد کنترل (DoerDoerDoer) باشد، مشروط بر اینکه واحد ایمنی (CheckerCheckerChecker) سیگنال تایید (ValidFlagValid FlagValidFlag) را صادر کرده باشد. در غیر این صورت، فرمان باید به حالت ایمن (Safe State / خاموش) برود.
